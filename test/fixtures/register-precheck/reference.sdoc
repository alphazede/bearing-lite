[DOCUMENT]
TITLE: Draft
[REQUIREMENT]
UID: REG-1
STATEMENT: >>>
When requested, the system shall report `tier_probability`.
<<<
RATIONALE: DEC-1; evidence.txt:1
VERIFICATION_METHOD: test
VERIFICATION_CASE: SEIT-1
DECISION: DEC-1
[RELATIONS]
TYPE: Parent
VALUE: REG-404
[/RELATIONS]
[/REQUIREMENT]
[REQUIREMENT]
UID: REG-2
STATEMENT: The system shall retain results.
VERIFICATION_METHOD: inspection
VERIFICATION_CASE: SEIT-2
DECISION: DEC-1
[/REQUIREMENT]
